; CAD Batch 0.3.0. Use only in a NEW EMPTY model. Command CBTESTFORMATS.
(defun cbaf:rect (x y w h)
 (entmakex (append (list '(0 . "LWPOLYLINE") '(100 . "AcDbEntity") '(8 . "CB_ALL_FORMATS") '(62 . 1) '(100 . "AcDbPolyline") '(90 . 4) '(70 . 1))
  (mapcar '(lambda (pt) (cons 10 pt)) (list (list x y) (list (+ x w) y) (list (+ x w) (+ y h)) (list x (+ y h)))))))
(defun cbaf:text (x y text)
 (entmakex (list '(0 . "TEXT") '(8 . "CB_ALL_FORMATS") '(62 . 5) (cons 10 (list x y 0.0)) '(40 . 7.0) (cons 1 text))))
(defun cbaf:line (x1 y1 x2 y2 color)
 (entmakex (list '(0 . "LINE") '(8 . "CB_ALL_FORMATS") (cons 62 color) (cons 10 (list x1 y1 0.0)) (cons 11 (list x2 y2 0.0)))))
(defun c:CBTESTFORMATS (/ formats i item x y oldecho)
 (if (ssget "_X" '((410 . "Model")))
  (princ "\nUse a NEW EMPTY drawing. Nothing was changed.")
  (progn
   (setq oldecho (getvar "CMDECHO")) (setvar "CMDECHO" 0) (setvar "TILEMODE" 1)
   (command "_.UNDO" "_Begin")
   (if (not (tblsearch "LAYER" "CB_ALL_FORMATS")) (entmake '((0 . "LAYER") (2 . "CB_ALL_FORMATS") (70 . 0) (62 . 7) (6 . "Continuous"))))
   (setq formats '(
      ("A4" 297.0 210.0)
      ("A3" 420.0 297.0)
      ("A2" 594.0 420.0)
      ("A1" 841.0 594.0)
      ("A0" 1189.0 841.0)
      ("A4x3" 630.0 297.0)
      ("A4x4" 841.0 297.0)
      ("A3x3" 891.0 420.0)
      ("A3x4" 1189.0 420.0)
      ("A3x5" 1486.0 420.0)
      ("A3x6" 1783.0 420.0)
      ("A3x7" 2080.0 420.0)
      ("A4x5" 1051.0 297.0)
      ("A4x6" 1261.0 297.0)
      ("A4x7" 1471.0 297.0)
      ("A4x8" 1682.0 297.0)
      ("A4x9" 1892.0 297.0)
      ("A2x3" 1261.0 594.0)
      ("A2x4" 1682.0 594.0)
      ("A2x5" 2102.0 594.0)
      ("A1x3" 1783.0 841.0)
      ("A1x4" 2378.0 841.0)
      ("A0x2" 1682.0 1189.0)
      ("A0x3" 2523.0 1189.0)
   ) i 0)
   (foreach item formats
    (setq x (* (rem i 6) 2700.0) y (* (- (fix (/ i 6))) 1400.0))
    (cbaf:rect x y (cadr item) (caddr item))
    (cbaf:text (+ x 20) (+ y 70) (strcat (car item) "  " (rtos (cadr item) 2 0) "x" (rtos (caddr item) 2 0) " mm"))
    (cbaf:line (+ x 20) (+ y 30) (+ x 120) (+ y 30) 3)
    (cbaf:line (+ x 20) (+ y 25) (+ x 20) (+ y 35) 5)
    (cbaf:line (+ x 120) (+ y 25) (+ x 120) (+ y 35) 5)
    (cbaf:text (+ x 20) (+ y 43) "100 mm")
    (setq i (1+ i)))
   (command "_.UNDO" "_End") (setvar "CMDECHO" oldecho) (command "_.ZOOM" "_Extents")
   (princ "\n24 formats ready. SAVE this DWG, then CADBATCH: Model ON, layer CB_ALL_FORMATS, scale 1, tolerance 2."))) (princ))
(princ "\nLoaded. In a NEW EMPTY drawing enter CBTESTFORMATS.") (princ)
