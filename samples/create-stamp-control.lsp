; CAD Batch 0.2.1 - upper title-block line scale fixture.
; NEW EMPTY metric drawing: APPLOAD, then CBTESTSTAMP.
; Frame layer CB_STAMP_FRAME. Stamp is deliberately on ANOTHER layer.
(defun cbs:point (x y scale angle ox oy)
  (list (+ ox (* scale (- (* x (cos angle)) (* y (sin angle)))))
        (+ oy (* scale (+ (* x (sin angle)) (* y (cos angle))))) 0.0))
(defun cbs:line (x1 y1 x2 y2 scale angle ox oy)
  (entmake (list '(0 . "LINE") '(8 . "CB_STAMP_LINES")
    (cons 10 (cbs:point x1 y1 scale angle ox oy))
    (cons 11 (cbs:point x2 y2 scale angle ox oy)))))
(defun cbs:frame (scale angle ox oy split / points x part)
  (setq points (mapcar '(lambda (p) (cbs:point (car p) (cadr p) scale angle ox oy))
    '((0.0 0.0) (420.0 0.0) (420.0 297.0) (0.0 297.0))))
  (entmake (append '((0 . "LWPOLYLINE") (100 . "AcDbEntity") (8 . "CB_STAMP_FRAME")
    (100 . "AcDbPolyline") (90 . 4) (70 . 1))
    (mapcar '(lambda (p) (cons 10 (list (car p) (cadr p)))) points)))
  ; Stamp: 185 x 55 mm, paper margins 5 mm right and bottom.
  (if split
    (progn (setq x 230.0)
      (foreach part '(10.0 10.0 10.0 10.0 15.0 10.0 120.0)
        (cbs:line x 60.0 (+ x part) 60.0 scale angle ox oy) (setq x (+ x part))))
    (cbs:line 230.0 60.0 415.0 60.0 scale angle ox oy))
  (cbs:line 230.0 5.0 415.0 5.0 scale angle ox oy)
  (cbs:line 230.0 5.0 230.0 60.0 scale angle ox oy)
  (cbs:line 415.0 5.0 415.0 60.0 scale angle ox oy)
  (cbs:line 230.0 15.0 415.0 15.0 scale angle ox oy)
  (cbs:line 230.0 35.0 415.0 35.0 scale angle ox oy)
  (cbs:line 230.0 50.0 415.0 50.0 scale angle ox oy)
  (entmake (list '(0 . "TEXT") '(8 . "CB_STAMP_LINES")
    (cons 10 (cbs:point 25.0 250.0 scale angle ox oy)) (cons 40 (* 8.0 scale))
    (cons 50 angle) (cons 1 (strcat "A3: geometry scale " (rtos scale 2 3))))))
(defun c:CBTESTSTAMP (/ oldecho)
  (if (tblsearch "LAYER" "CB_STAMP_FRAME")
    (princ "\nFixture already exists. Start a NEW EMPTY drawing.")
    (progn
      (setq oldecho (getvar "CMDECHO")) (setvar "CMDECHO" 0)
      (command "_.UNDO" "_Begin")
      (entmake '((0 . "LAYER") (2 . "CB_STAMP_FRAME") (70 . 0) (62 . 7) (6 . "Continuous")))
      (entmake '((0 . "LAYER") (2 . "CB_STAMP_LINES") (70 . 0) (62 . 3) (6 . "Continuous")))
      (cbs:frame 1.0 0.0 0.0 0.0 nil)
      (cbs:frame 10.0 0.0 1000.0 0.0 T)
      (cbs:frame 100.0 0.0 10000.0 0.0 nil)
      (cbs:frame 37.5 (/ pi 12.0) 0.0 40000.0 nil)
      (command "_.UNDO" "_End") (setvar "CMDECHO" oldecho)
      (command "_.ZOOM" "_Extents")
      (princ "\nReady: CB_STAMP_FRAME; manual scales=1; stamp mode ON => 4 A3 frames: 1, 10, 37.5, 100.")))
  (princ))
(princ "\nLoaded stamp fixture. In a NEW EMPTY drawing enter CBTESTSTAMP.")
(princ)
