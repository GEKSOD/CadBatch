; CAD Batch 0.1 - creates a synthetic test drawing in the CURRENT document.
; Use a NEW EMPTY drawing. Command: CBTESTDRAW. ASCII source for all CAD locales.
; Expected: 8 unique frames with scales 1;100, one coincident contour warning.
(defun cb:point (x y angle ox oy)
  (list (+ ox (- (* x (cos angle)) (* y (sin angle))))
        (+ oy (+ (* x (sin angle)) (* y (cos angle))))))
(defun cb:poly (points layer)
  (entmake (append (list '(0 . "LWPOLYLINE") '(100 . "AcDbEntity")
    (cons 8 layer) '(100 . "AcDbPolyline") (cons 90 (length points)) '(70 . 1))
    (mapcar '(lambda (p) (cons 10 p)) points))))
(defun cb:text (x y h label layer)
  (entmake (list '(0 . "TEXT") (cons 8 layer) (cons 10 (list x y 0.0))
    (cons 40 h) (cons 1 label))))
(defun cb:frame (x y w h angle layer label / pts)
  (setq pts (mapcar '(lambda (p) (cb:point (car p) (cadr p) angle x y))
    (list '(0.0 0.0) (list w 0.0) (list w h) (list 0.0 h))))
  (cb:poly pts layer)
  (if (= angle 0.0) (cb:text (+ x (* w 0.05)) (+ y (* h 0.1)) (* h 0.035) label layer)))
(defun cb:insert (name x y angle layer)
  (entmake (list '(0 . "INSERT") (cons 8 layer) (cons 2 name)
    (cons 10 (list x y 0.0)) '(41 . 1.0) '(42 . 1.0) '(43 . 1.0) (cons 50 angle))))
(defun c:CBTESTDRAW (/ oldecho)
  (if (or (tblsearch "BLOCK" "CB_TEST_A4") (tblsearch "BLOCK" "CB_TEST_OUTER"))
    (princ "\nTest blocks already exist. Start a new empty drawing.")
    (progn
      (setq oldecho (getvar "CMDECHO"))
      (setvar "CMDECHO" 0)
      (command "_.UNDO" "_Begin")
      (entmake '((0 . "LAYER") (2 . "CB_TEST") (70 . 0) (62 . 7) (6 . "Continuous")))
      (cb:frame 0.0 0.0 297.0 210.0 0.0 "CB_TEST" "A4 - control line: 100 mm")
      (entmake '((0 . "LINE") (8 . "CB_TEST") (10 20.0 60.0 0.0) (11 120.0 60.0 0.0)))
      (cb:frame 500.0 0.0 420.0 297.0 0.0 "CB_TEST" "A3")
      (cb:frame 1100.0 0.0 297.0 420.0 0.0 "CB_TEST" "A3 portrait")
      (cb:frame 1600.0 0.0 594.0 420.0 0.0 "CB_TEST" "A2")
      (cb:frame 0.0 800.0 420.0 297.0 (/ pi 6.0) "CB_TEST" "A3 rotated")
      (entmake '((0 . "BLOCK") (8 . "0") (2 . "CB_TEST_A4") (70 . 0) (10 0.0 0.0 0.0)))
      (cb:frame 0.0 0.0 297.0 210.0 0.0 "0" "A4 inside block")
      (entmake '((0 . "ENDBLK") (8 . "0")))
      (cb:insert "CB_TEST_A4" 700.0 800.0 0.0 "CB_TEST")
      (entmake '((0 . "BLOCK") (8 . "0") (2 . "CB_TEST_INNER") (70 . 0) (10 0.0 0.0 0.0)))
      (cb:frame 0.0 0.0 420.0 297.0 0.0 "0" "A3 nested block")
      (entmake '((0 . "ENDBLK") (8 . "0")))
      (entmake '((0 . "BLOCK") (8 . "0") (2 . "CB_TEST_OUTER") (70 . 0) (10 0.0 0.0 0.0)))
      (cb:insert "CB_TEST_INNER" 20.0 20.0 0.0 "0")
      (entmake '((0 . "ENDBLK") (8 . "0")))
      (cb:insert "CB_TEST_OUTER" 1300.0 800.0 (/ pi 12.0) "CB_TEST")
      (cb:frame 10000.0 10000.0 42000.0 29700.0 0.0 "CB_TEST" "A3 - geometry scale 100")
      ; Duplicate of the first frame, plus two non-matching objects.
      (cb:poly '((0.0 0.0) (297.0 0.0) (297.0 210.0) (0.0 210.0)) "CB_TEST")
      (cb:frame 2500.0 0.0 123.0 77.0 0.0 "CB_TEST" "Not a paper format")
      (cb:poly '((0.0 1500.0) (420.0 1500.0) (400.0 1797.0) (0.0 1797.0)) "CB_TEST")
      (command "_.UNDO" "_End")
      (setvar "CMDECHO" oldecho)
      (command "_.ZOOM" "_Extents")
      (princ "\nCAD Batch test ready: scales 1;100 => 8 unique frames, 1 overlap warning.")))
  (princ))
(princ "\nLoaded CAD Batch test generator. In a NEW EMPTY drawing enter CBTESTDRAW.")
(princ)
