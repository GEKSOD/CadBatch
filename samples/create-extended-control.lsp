; CAD Batch 0.2 - additional native geometry fixture, ASCII-only source.
; In a NEW EMPTY drawing: APPLOAD this file, then CBTESTMORE.
; Expected with layer CB_MORE*, scale 1 and LINE search ON: three A3 frames.
(defun cbm:line (x1 y1 x2 y2 layer)
  (entmake (list '(0 . "LINE") (cons 8 layer)
    (cons 10 (list x1 y1 0.0)) (cons 11 (list x2 y2 0.0)))))
(defun cbm:text (x y text layer)
  (entmake (list '(0 . "TEXT") (cons 8 layer) (cons 10 (list x y 0.0))
    '(40 . 12.0) (cons 1 text))))
(defun c:CBTESTMORE (/ oldecho)
  (if (tblsearch "LAYER" "CB_MORE_LINES")
    (princ "\nFixture already exists. Start a NEW EMPTY drawing.")
    (progn
      (setq oldecho (getvar "CMDECHO"))
      (setvar "CMDECHO" 0)
      (command "_.UNDO" "_Begin")
      (entmake '((0 . "LAYER") (2 . "CB_MORE_LINES") (70 . 0) (62 . 1) (6 . "Continuous")))
      (entmake '((0 . "LAYER") (2 . "CB_MORE_OLD") (70 . 0) (62 . 3) (6 . "Continuous")))
      ; Four separate lines: A3 at origin.
      (cbm:line 0.0 0.0 420.0 0.0 "CB_MORE_LINES")
      (cbm:line 420.0 0.0 420.0 297.0 "CB_MORE_LINES")
      (cbm:line 420.0 297.0 0.0 297.0 "CB_MORE_LINES")
      (cbm:line 0.0 297.0 0.0 0.0 "CB_MORE_LINES")
      (cbm:text 20.0 30.0 "A3 - four LINE objects" "CB_MORE_LINES")
      ; Segmented lower side: A3 at x=600.
      (cbm:line 600.0 0.0 810.0 0.0 "CB_MORE_LINES")
      (cbm:line 810.0 0.0 1020.0 0.0 "CB_MORE_LINES")
      (cbm:line 1020.0 0.0 1020.0 297.0 "CB_MORE_LINES")
      (cbm:line 1020.0 297.0 600.0 297.0 "CB_MORE_LINES")
      (cbm:line 600.0 297.0 600.0 0.0 "CB_MORE_LINES")
      (cbm:text 620.0 30.0 "A3 - split side" "CB_MORE_LINES")
      ; Legacy POLYLINE + VERTEX/SEQEND: A3 at x=1200.
      (entmake '((0 . "POLYLINE") (8 . "CB_MORE_OLD") (66 . 1) (70 . 1) (10 0.0 0.0 0.0)))
      (foreach pt '((1200.0 0.0 0.0) (1620.0 0.0 0.0) (1620.0 297.0 0.0) (1200.0 297.0 0.0))
        (entmake (list '(0 . "VERTEX") '(8 . "CB_MORE_OLD") (cons 10 pt) '(70 . 0))))
      (entmake '((0 . "SEQEND") (8 . "CB_MORE_OLD")))
      (cbm:text 1220.0 30.0 "A3 - legacy POLYLINE" "CB_MORE_OLD")
      (command "_.UNDO" "_End")
      (setvar "CMDECHO" oldecho)
      (command "_.ZOOM" "_Extents")
      (princ "\nCBTESTMORE ready: layer CB_MORE*, scale 1, LINE search ON => 3 A3 frames.")))
  (princ))
(princ "\nLoaded extended CAD Batch fixture. In a NEW EMPTY drawing enter CBTESTMORE.")
(princ)
